module opmdc {
    yang-version 1;
    namespace "urn:opendaylight:params:xml:ns:yang:opmdc";
    prefix "opmdc";

    revision "2015-01-05" {
        description "Initial revision of opmdc model";
    }
}
